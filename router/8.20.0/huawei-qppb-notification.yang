/*
Copyright (C) 2019 Huawei Technologies Co., Ltd. All rights reserved.
*/
module huawei-qppb-notification {
  yang-version 1;
  namespace "urn:huawei:yang:huawei-qppb-notification";
  prefix qppb-notification;
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of qppb.";
  revision 2019-11-06 {
    description
      "Initial revision.";
    reference
      "Huawei private.";
  }
  ext:task-name "qos";
  typedef qppb-direction-type {
    type enumeration {
      enum "inbound" {
        value 1; 
        description
          "Inbound.";
      }
      enum "outbound" {
        value 2; 
        description
          "Outbound.";
      }
    }
    description
      "Direction type.";
  }
  notification xqos-interface-qppb-delete-alarm {
    description
      "The QPPB policy on the interface is deleted or does not take effect.";
    leaf interface-name {
      type string {
        length "1..511";
      }
      description
        "Interface name.";
    }
    leaf policy-name{
      type string {
        length "1..31";
      }
      description
        "Policy name.";
    }
    leaf direction {
      type qppb-direction-type;
      description
        "Direction. - 1: inbound - 2: outbound.";
    }
    leaf description {
      type string {
        length "1..128";
      }
      description
        "Precautions information.";
    }
  }
}
